# BMS_SRS
Software Requirements Document "Battery Management System (BMS)"

1. Introduction
1.1 Purpose
This document defines the software requirements for the Battery Management System (BMS). The BMS ensures safe, efficient, and reliable operation of a battery module comprising multiple cells.
1.2 Scope
The BMS software interfaces with the charger, inverter, and precharge circuit. It manages battery state estimation, fault detection, balancing, charging, discharging, and power distribution. The system supports a 3-cell battery pack.
1.3 Definitions, Acronyms, and Abbreviations
    * BMS: Battery Management System
    * SOC: State of Charge
    * SOH: State of Health
    * Vfb: Vehicle Feedback Interface
    * Stateflow: MATLAB tool for state machine modeling
    * Precharge Circuit: Safely charges capacitors on system startup

## #1: General Requirements (Container)

### #2: Battery Module Management (Container)

#### #3: Battary_No (Functional)
The BMS shall manage the operation of a 3-cell battery module.

#### #4: Battary_Limit (Functional)
The battery voltage shall operate within the range of 9V to 16.8V, in accordance with the safe operating limits of 3.0V - 4.2V lithium-ion battery cells.

### #5: Safety and Efficiency (Functional)
The BMS shall detect and protect the battery from unsafe conditions such as over-voltage, under-voltage, over-temperature, and short circuits.

#### #6: Over-voltage (Functional)
Over-voltage: 4.2V per cell (total 12.6V).

#### #7: Under-voltage (Functional)
Under-voltage: 3.0V per cell (total 9.0V).

#### #8: Over-temperature (Functional)
Over-temperature: 60°C.

#### #9: Under-temperature (Functional)
Under-temperature: -20°C.

#### #10: Charging Over-Current (Functional)
Charging Over-Current shall not exceed 15A maximum.

#### #11: Discharging Over-Current (Functional)
Discharging Over-Current shall not exceed 30A maximum.

### #12: System Interfaces (Container)

#### #13: Charging and Discharging (Functional)
The BMS shall regulate charging and discharging processes to maximize efficiency and extend battery life.

#### #22: System Interfaces (Functional)
The BMS shall provide robust interfaces to support integration with external systems, including but not limited to chargers, inverters, and precharge circuits.

## #23: Functional Interfaces (Container)

### #14: BMS INPUTS (Container)
BMS INPUTS
| Port Interface | Data Element | Type | Units | Description |
| --- | --- | --- | --- | --- |
| VfbStateRequest | StateRequest | Enum | - | Request from vehicle network |
| VfbCellVoltages | CellVoltage | Float32 | V | Voltage of each cell |
| VfbCellTemperatures | CellTemperature | Float32 | °C | Temperature of each cell |
| VfbPackVoltage | TotalPackVoltage | Float32 | V | Total voltage of battery pack |
| VfbPackCurrent | PackCurrent | Float32 | A | Current flowing through pack |
| VfbChargerVoltageOutput | ChargerOutputVoltage | Float32 | V | Output voltage from charger |
| VfbInverterVoltageOutput | InverterOutputVoltage | Float32 | V | Output voltage to inverter |

#### #15: State Request (Functional)
The BMS shall accept a State Request from the vehicle network to define the operational state.
(State: Balancing-Charging-Driving)
| Name | Data Element | Data Type | Unit | Range |
| --- | --- | --- | --- | --- |
| VfbStateRequest | StateRequest | Enum | - | [0 : 2] |

#### #16: Cell Voltages (Functional)
The BMS shall receive individual voltage measurements for each cell block (cells in series) at sample rate of 10KHz.
| Name | Data Element | Data Type | Unit | Range | Dimension |
| --- | --- | --- | --- | --- | --- |
| VfbCellVoltages | CellVoltage | Float32 | V | 0V to 5V per cell | # Cells |

#### #17: Cell Temperatures (Functional)
The BMS shall receive temperature readings for each cell block (cells in series) at sample rate of 10KHz.
| Name | Data Element | Data Type | Unit | Range | Dimension |
| --- | --- | --- | --- | --- | --- |
| VfbCellTemperatures | CellTemperature | Float32 | °C | -10°C to 60°C | # Cells |

#### #18: Pack Voltage (Functional)
The BMS shall receive the total voltage of the battery pack terminals (+Ve Batt and -Ve Batt) at sample rate of 10KHz.
| Name | Data Element | Data Type | Unit | Range |
| --- | --- | --- | --- | --- |
| VfbPackVoltage | TotalPackVoltage | Float32 | V | 0V to 120V |

#### #19: Pack Current (Functional)
The BMS shall receive the total current flowing through the battery pack at sample rate of 10KHz.
- VfbPackCurrent > 0 indicates battery pack charging.
- VfbPackCurrent < 0 indicates battery pack discharging.
| Name | Data Element | Data Type | Unit | Range |
| --- | --- | --- | --- | --- |
| VfbPackCurrent | PackCurrent | Float32 | A | -30A to 30A |

#### #20: Charger Voltage (Functional)
TheBMS shall receive the charger output voltage.
| Name | Data Element | Data Type | Unit | Range |
| --- | --- | --- | --- | --- |
| VfbChargerVoltageOutput | ChargerOutputVoltage | Float32 | V | -180V to 180V |

#### #21: Inverter Voltage (Functional)
The BMS shall receive the inverter output voltage.
| Name | Data Element | Data Type | Unit | Range |
| --- | --- | --- | --- | --- |
| VfbInverterVoltageOutput | InverterOutputVoltage | Float32 | V | -180V to 180V |

### #26: BMS OUTPUTS (Container)
BMS OUTPUTS
| Port Interface | Data Element | Type | Units | Description |
| --- | --- | --- | --- | --- |
| VfbStateOfCharge | StateOfCharge | Float32 | % | Calculated state of charge |
| VfbBmsOperationalState | OperationalState | Enum | - | Current operational state |
| VfbCurrentLimits | CurrentLimits | Float32 | A | Computed current limitations |
| VfbBalanceCommands | BalanceCommand | Boolean | - | Commands to balance cell charge |
| VfbChargeCurrentCmd | ChargeCurrentCommand | Float32 | A | Command current for charging |
| VfbContactorCmds | ContactorCommand | Boolean | - | Command‎s to manage contactors |

#### #27: State of Charge (SOC) (Functional)
The BMS shall output the State of Charge (SOC) as a percentage of battery charge.
| Name | Data Element | Data Type | Unit | Range |
| --- | --- | --- | --- | --- |
| VfbStateOfCharge | StateOfCharge | Float32 | % | 0% to 100% |

#### #28: Operational State (Functional)
The BMS shall output the current operational state.
(State: Standby-Charging-Discharging-Fault)
| Name | Data Element | Data Type | Unit | Range |
| --- | --- | --- | --- | --- |
| VfbBmsOperationalState | OperationalState | Enum | - | [0 - 3] |

#### #29: Current Limits (Functional)
The BMS shall output the calculated current limits.
| Name | Data Element | Data Type | Unit | Range |
| --- | --- | --- | --- | --- |
| VfbCurrentLimits | CurrentLimits | Float32 | A | -30A to 30A |

#### #30: Balancing Commands (Functional)
The BMS shall output a Boolean array indicating the cell balancing commands.
| Name | Data Element | Data Type | Unit | Range |
| --- | --- | --- | --- | --- |
| VfbBalanceCommands | BalanceCommand | Boolean | - | - |

#### #31: Charge Current Command (Functional)
The BMS shall output the current command for charging the battery.
| Name | Data Element | Data Type | Unit | Range |
| --- | --- | --- | --- | --- |
| VfbChargeCurrentCmd | ChargeCurrentCommand | Float32 | A | 0A to 15A |

#### #32: Contactor Command (Functional)
The BMS shall output a Boolean array indicating the contactor commands.
contactor for:
- Positive pole of the Charger
- Negative pole of the Charger
- Pre-charge of the Charger
- Positive pole of the Inverter
- Negative pole of the Inverter
- Pre-charge of the Inverter
| Name | Data Element | Data Type | Unit | Range |
| --- | --- | --- | --- | --- |
| VfbContactorCmds | ContactorCommand | boolean | - | - |

## #33: Software Architecture (Functional)
The BMS software shall have a modular architecture for easy maintenance and upgrades.
The BMS software shall be divided in this Modules:
1. Main State Machine
2. Current Limits Calculation
3. SOC/SOH Estimation
4. Balancing Logic

### #34: Main State Machine (Container)
The BMS shall execute the Main State Machine every 50 ms.
The Main State Machine has 4 main functionalities:
1. Manage the BMS status evolution on driving requests and safety
2. Calculate the correct charging mode
3. Monitors current, voltage and temperature faults for safty
4. Securely close and open the contacts to the charger and inverter

#### #71: BMS Main State Machine: Interfaces (Container)

##### #72: Inputs (Functional)
BMS MAIN STATE MACHINE INPUTS
| Port Interface | Data Element | Type | Units | Description |
| --- | --- | --- | --- | --- |
| VfbStateRequest | StateRequest | Enum | - | Request from vehicle network |
| VfbCellVoltages | CellVoltage | Float32 | V | Voltage of each cell |
| VfbCellTemperatures | CellTemperature | Float32 | °C | Temperature of each cell |
| VfbPackVoltage | TotalPackVoltage | Float32 | V | Total voltage of battery pack |
| VfbPackCurrent | PackCurrent | Float32 | A | Current flowing through pack |
| VfbChargerVoltageOutput | ChargerOutputVoltage | Float32 | V | Output voltage from charger |
| VfbInverterVoltageOutput | InverterOutputVoltage | Float32 | V | Output voltage to inverter |
| VfbCurrentLimits | CurrentLimits | Float32 | A | Current Limits for safety |
| VfbMaxCellVoltage | MaxCellVoltage | Float32 | V | Max Cell Voltage Limits for safety |
| VfbMinCellVoltage | MinCellVoltage | Float32 | V | Max Voltage Limits for safety |

##### #73: Outputs (Functional)
BMS MAIN STATE MACHINE OUTPUTS
| Port Interface | Data Element | Type | Units | Description |
| --- | --- | --- | --- | --- |
| VfbBmsOperationalState | OperationalState | Enum | - | Current operational state |
| VfbChargeCurrentReq | ChargeCurrentReq | Boolean | - | Request to the charger |
| VfbContactorCmds | ContactorCommand | Boolean | - | Commands to manage contactors |

#### #74: BMS State calculation (Functional)
The Main State Machine shall support accurate state transitions between the BMS Mode (Standby - Charging - Driving - State) based on State Request, Relay Contactors States (Charger and Inverter), and Fault.

#### #75: Charging Mode calculation (Functional)
The Main State Machine shall support accurate state transitions between the Chargin Mode (Init - Constant Current "CC" - Constant Voltage "CV")

#### #76: Relay Charger Commands (Functional)
The Main State Machine shall support accurate Opening and closing for the Relays (Pre-charger, Positive, and Negative) for the Charger

#### #77: Relay Inverter Commands (Functional)
The Main State Machine shall support accurate Opening and closing for the Relays (Pre-charger, Positive, and Negative) for the Inverter

#### #78: Fault Monitor Calculation (Functional)
The Main State Machine shall detect the Faults of :
- Current Limitations "Over Current Pack Faut"
- Voltages Limitations "Over/Under Voltage Pack Faut"
- Temperature Limitaions "High/Low Cell Temperature Faut"

### #35: Current Limits Calculation (Functional)
The BMS shall calculate current limits every 100 ms.
The Current Limit Calculation must calculate Minimum and Maximum Cell Voltage and the Current limits.

#### #79: BMS Current Limit Calculation: Interfaces (Container)

##### #80: Inputs (Functional)
BMS CURRENT LIMIT CALCULATION INPUTS
| Port Interface | Data Element | Type | Units | Range |
| --- | --- | --- | --- | --- |
| VfbCellVoltages | CellVoltage | Float32 | V | 3.0V to 4.2V per cell |
| VfbCellTemperatures | CellTemperature | Float32 | °C | -10°C to 60°C |

##### #81: Outputs (Functional)
BMS CURRENT LIMIT CALCULATION OUTPUTS
| Port Interface | Data Element | Type | Units | Description |
| --- | --- | --- | --- | --- |
| VfbCurrentLimits | CurrentLimits | Float32 | A | Current Limits for safety |
| VfbMaxCellVoltage | MaxCellVoltage | Float32 | V | Max Cell Voltage Limits for safety |
| VfbMinCellVoltage | MinCellVoltage | Float32 | V | Max Voltage Limits for safety |

#### #82: BMS Current Limit Calculation: Min/Max Calculation (Functional)
The BMS shall calculate the Min/Max Voltages between cells.

#### #83: BMS Current Limit Calculation: Charge/Discharge Current Limit (Functional)
The BMS shall calculate the Charge/Discharge Current Limit with ±0.01A resolution.

### #36: SOC Estimation (Functional)
The BMS shall estimate SOC every 200 ms.
The State Of Carge Estimation shall estimate SOC with a resolution of 1% and accuracy of ±3%. (SOC_CC, SOC_KF, SOC_EKF).

#### #84: BMS SOC Estimation: Interfaces (Container)

##### #85: Inputs (Functional)
BMS SOC ESTIMATION INPUTS
| Port Interface | Data Element | Type | Units | Description |
| --- | --- | --- | --- | --- |
| VfbCellTemperatures | CellTemperature | Float32 | °C | Temperature of each cell |
| VfbCellVoltages | CellVoltage | Float32 | V | Voltage of each cell |
| VfbPackCurrent | PackCurrent | Float32 | A | Current flowing through pack |

##### #86: Outputs (Functional)
BMS SOC ESTIMATION OUTPUTS
| Port Interface | Data Element | Type | Units | Description |
| --- | --- | --- | --- | --- |
| VfbStateOfCharge | StateOfCharge | Float32 | % | Calculated state of charge |

#### #87: BMS SOC Estimation: Coulomb Counting (Functional)
The BMS shall calculate the SOC with Coulomb Counting following the Req.

#### #88: BMS SOC Estimation: SOC OCV (Functional)
The BMS shall drift correction of the SOC when the Battery resting with OCV following the Req.

##### #89: BMS SOC Estimation: SOC UKF, EKF (Informational)
The BMS shall calculate the SOC with UKF, and EKF following the Req.

### #37: SOH Estimation (Functional)
The BMS shall estimate SOH every 200 ms.
The State Of Health Estimation shall estimate SOH with a resolution of 1% and accuracy of ±3%. (SOH_CC, SOH_KF, SOH_EKF).

#### #90: BMS SOH Estimation: Interfaces (Container)

##### #91: Inputs (Functional)
BMS SOH ESTIMATION INPUTS
| Port Interface | Data Element | Type | Units | Description |
| --- | --- | --- | --- | --- |
| VfbCellTemperatures | CellTemperature | Float32 | °C | Temperature of each cell |
| VfbCellVoltages | CellVoltage | Float32 | V | Voltage of each cell |
| VfbPackCurrent | PackCurrent | Float32 | A | Current flowing through pack |

##### #92: Outputs (Functional)
BMS SOH ESTIMATION OUTPUTS
| Port Interface | Data Element | Type | Units | Description |
| --- | --- | --- | --- | --- |
| VfbStateOfHealth | StateOfHealth | Float32 | % | Calculated state of charge |

#### #93: BMS SOH Estimation: Coulomb Counting (Functional)
The BMS shall calculate the SOH with accumulted the Discharge charges following the Req.

##### #94: BMS SOH Estimation: SOC UKF (Informational)
The BMS shall calculate the SOH with UKF following the Req.

##### #95: BMS SOH Estimation: SOC EKF (Informational)
The BMS shall calculate the SOH with EKF following the Req.

### #38: Balancing Logic (Functional)
The BMS shall execute balancing logic every 250 ms.
The Balancing Logic shall securely close and open the contacts to the charger and inverter.

#### #96: BMS Balancing Logic Interfaces (Container)

##### #97: Inputs (Functional)
BMS BALANCING LOGIC INPUTS
| Port Interface | Data Element | Type | Units | Description |
| --- | --- | --- | --- | --- |
| VfbStateRequest | StateRequest | Enum | - | Request from vehicle network |
| VfbCellVoltages | CellVoltage | Float32 | V | Voltage of each cell |
| VfbMaxCellVoltage | MaxCellVoltage | Float32 | V | Max Cell Voltage Limits for safety |
| VfbMinCellVoltage | MinCellVoltage | Float32 | V | Max Voltage Limits for safety |

##### #98: Outputs (Functional)
BMS BALANCING LOGIC OUTPUTS
| Port Interface | Data Element | Type | Units | Description |
| --- | --- | --- | --- | --- |
| VfbBalanceCommands | BalanceCommand | Boolean | - | Commands to balance cell charge |

#### #99: BMS Balancing Logic: Balancing Voltage Difference (Functional)
The BMS shall balance cell levels when voltage difference exceeds the configured Threshold.
- Default Start Threshold Value: 25 mV (0.025 V)
- Default Stop Threshold Value: 10 mV (0.010 V)

#### #100: BMS Balancing Logic: Balancing ON/OFF (Functional)
the Balancing Logic shall send the command to activate/deactivate the balancing Process.

### #66: User Interface (Container)

#### #105: User Interface: Monitoring and Configuration (Functional)
The BMS shall provide a user interface that facilitates both monitoring of system status and configuration of operational parameters.

#### #106: User Interface: Alerts and Notifications (Functional)
The BMS shall provide visual and audible alerts to notify users of any critical alarms or warnings.

#### #107: User Interface: Configuration (Functional)
The BMS shall provide a user interface that enables users to configure settings, including charging profiles and fault thresholds.

#### #108: User Interface: Diagnostics (Functional)
The BMS shall supply comprehensive diagnostic information to facilitate maintenance and troubleshooting activities.

## #39: Reliability and Maintainability (Container)

### #40: Self-Calibration (Functional)
The BMS shall calibrate sensors at least every 48 hours or when temperature changes by 5°C.

### #41: Self-Diagnostics (Functional)
The BMS shall perform self-diagnostics periodically to detect component failures.

### #65: Fault Tolerance (Container)
The BMS shall remain operational during minor component failures by employing fault-tolerant mechanisms.

#### #101: Voltage Cell Monitoring (Functional)
The BMS shall monitor cell voltages in real time with Voltage accuracy: ±0.05V.

#### #102: Temperature Cell Monitoring (Functional)
The BMS shall monitor cell temperatures in real time with Temperature accuracy: ±1°C.

#### #103: Package Currunt Monitoring (Functional)
The BMS shall monitor Package Currunt in real time with Voltage accuracy: ±0.01A.

#### #104: Package Voltage Monitoring (Functional)
The BMS shall monitor Package Voltage in real time with Voltage accuracy: ±0.1V.

## #42: Communication Requirements (Functional)

### #43: Communication Protocols (Functional)
The BMS shall support standard MODBUS communication protocols for interfacing with external devices (e.g., vehicle network, charger, inverter).

### #44: Communication Latency (Functional)
The BMS shall ensure that communication latency does not exceed 100 milliseconds.

### #45: Communication Interfaces (Functional)
The BMS shall have an API or diagnostic interface accessible via Bluetooth or USB for data logging, diagnostics, and system configuration.

### #46: Data Reporting (Functional)
The BMS shall report key system parameters (SOC, temperature, voltage, current, etc.) to external devices in real-time.

### #111: Security (Container)

#### #112: Data Security (Functional)
The BMS shall secure communication and data using Advanced Encryption Standard (AES).

#### #113: Access Control (Functional)
The BMS shall incorporate robust access control mechanisms to prevent unauthorized access to its system functionalities and data.

## #47: Logging and Data Recording (Container)

### #48: Error Recording (Functional)
The BMS shall log the error codes of the detected fault event.

### #55: Operational Data Recording (Functional)
The BMS shall log operational data, including cell voltage, current, temperature, and SOC, with a minimum frequency of 1 Hz for analysis and diagnostics.

### #56: Recording Limit (Functional)
Logs must be stored for a minimum of 30 days and should be accessible via diagnostic interfaces.

## #57: Software Updates (Container)

### #58: Updates_Req (Functional)
The BMS shall support over-the-air (OTA) software updates with secure mechanisms to avoid unauthorized access.

### #59: Updates_Limit (Functional)
Updates shall be applied with minimal downtime, not exceeding 30 seconds.

## #60: Fault Notifications (Container)

### #61: Fault Detection (Functional)
The BMS shall detect system fault event (specifically over-voltage, under-voltage, over-temperature, and short circuits).

### #62: Fault Response (Functional)
The BMS shall initiate a response within 50 milliseconds of fault detection.

### #63: Fault Code (Functional)
The BMS shall notify users of critical faults and provide error codes for troubleshooting.

### #64: Fault Notifications (Functional)
The BMS shall provide notifications for system faults (e.g., over-voltage, short circuit) via both visual and audible alerts, with a response time of less than 100 ms.

## #67: Acceptance Criteria (Container)

### #68: Functional Safety (Functional)
The BMS shall be designed, implemented, and validated in accordance with the ISO 26262 functional safety standard, ensuring that all relevant safety measures and protocols are rigorously adhered to.

### #69: Regulatory Compliance (Functional)
The BMS shall comply with all applicable regulatory requirements for automotive and energy storage applications by leveraging Model Advisor in accordance with MAAB guidelines, thereby ensuring full conformance with industry standards and governmental regulations.

### #70: Acceptance Criteria (Container)

#### #109: Real-World Performance (Functional)
The BMS shall undergo rigorous testing in real-world scenarios, including edge cases such as high temperatures and sudden load changes, to validate its reliability and performance.

#### #110: Documentation and Independent Verification (Functional)
Comprehensive test plans, procedures, and independent verification reports shall confirm that all acceptance criteria are met.
